module iana-template {
  yang-version 1.1;

  // replace this string with a unique namespace URN value

  namespace "urn:ietf:params:xml:ns:yang:iana-template";

  // replace with the assigned prefix

  prefix iana-foo;

  organization
    "Internet Assigned Numbers Authority (IANA)";

  contact
    "Internet Assigned Numbers Authority

     ICANN
     12025 Waterfront Drive, Suite 300
     Los Angeles, CA 90094

     Tel: +1 424 254 5300

     <mailto:iana@iana.org>";

  description
    "This module defines a template for IANA-maintained modules.

     Copyright (c) <insert year> IETF Trust and the persons 
     identified as authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     The initial version of this YANG module is part of RFC IIII; 
     see the RFC itself for full legal notices.

  // RFC Ed.: replace IIII with actual RFC number and remove
  // this note

  // If a script is used, complete with the script information

     This version of this YANG module was generated from the
     corresponding IANA registry using a <script-info>.

  // RFC Ed.: replace the IANA_FOO_URL and remove this note

     The latest version of this YANG module is available at
     <IANA_FOO_URL>.";

  // replace with the registry name and the URL of the IANA registry

  reference
    "Registry Name (URL)";


  // replace 'date-revision' with the module publication date
  // the format is (YYYY-MM-DD)

  revision date-revision {
    description
      "Indicates the list of changes per Section 4.30.3 of RFCAAAA.";
    reference
      "URL of the latest version of the module
       (if any) list the authoritative event (e.g., RFC) that 
       triggered the update to the YANG module";
  }

  // replace 'date-initial' with the module publication date
  // the format is (YYYY-MM-DD)

  revision date-initial {
    description
      "Initial version";
    reference
      "URL of the published initial version of the module
       RFC IIII: RFC Title";

  // RFC Ed.: Update with the RFC number and title 
  // of the RFC that defined the initial version of
  // the module and remove this note
  }

  // identity statements
  // typedef statements
}
